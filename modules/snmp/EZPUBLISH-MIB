EZSYSTEMS-MIB DEFINITIONS ::= BEGIN

IMPORTS
        enterprises,
        MODULE-IDENTITY
                FROM SNMPv2-SMI
        OBJECT-TYPE
                FROM RFC-1212
        DisplayString
                FROM RFC1213-MIB;

-- The assignments

eZSystemsMIB MODULE-IDENTITY
        LAST-UPDATED "200905260000Z"
        ORGANIZATION "eZ Systems"
        CONTACT-INFO
                "Gaetano Giunta
                email: gg@ez.no"
        DESCRIPTION
                "This MIB module contains application specific
                managed objects for the eZ Publish CMS server."
        REVISION "2009009090000Z"
        DESCRIPTION
                "Fixed mib compliance; renamed root to eZSystems"
        REVISION "200905260000Z"
        DESCRIPTION
                "Added the complete settings subtree; reshuffled and expanded status subtree; more conforming SMIv2 mib"
        REVISION "200903130000Z"
        DESCRIPTION
                "Corrected datetimes in MIB."
        REVISION "200902240000Z"
        DESCRIPTION
                "Added info oid."
        REVISION "200902220000Z"
        DESCRIPTION
                "The intial version."

        ::= { enterprises 33120 }

-- a truth value
Boolean ::=   INTEGER { true(1), false(2) }

eZPublish       OBJECT IDENTIFIER ::= {eZSystemsMIB 1}

-- a branch where other extensions can add their oid
-- general rule: one new oid per extension below eZPublishMIB.eZPublish.extensions
extensions      OBJECT IDENTIFIER ::= {eZPublish 4}
