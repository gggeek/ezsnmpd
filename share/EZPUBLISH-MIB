EZSYSTEMS-MIB DEFINITIONS ::= BEGIN

IMPORTS
        enterprises,
        MODULE-IDENTITY
                FROM SNMPv2-SMI
        OBJECT-TYPE
                FROM RFC-1212
        DisplayString
                FROM RFC1213-MIB;

-- The assignments

eZSystemsMIB MODULE-IDENTITY
        LAST-UPDATED "201002080000Z"
        ORGANIZATION "eZ Systems"
        CONTACT-INFO
                "Gaetano Giunta
                email: gg@ez.no"
        DESCRIPTION
                "This MIB module contains application specific
                managed objects for the eZ Publish CMS server."
        REVISION "201002080000Z"
        DESCRIPTION
                "mib file sorted differently because of changes in underlying code. Settings oids have been renamed to improve smilint compliance"
        REVISION "201001080000Z"
        DESCRIPTION
                "changed shop orders per status info oids in status handler into a table format"
        REVISION "200911240000Z"
        DESCRIPTION
                "Added cache files info in status handler;
                added shop orders per status info in status handler;
                fixed mib compliance;
                added md5 of exact version in a comment line;
                fixed settings mib to be SMIv2 compliant"
        REVISION "200909090000Z"
        DESCRIPTION
                "Fixed mib compliance; renamed root to eZSystems"
        REVISION "200905260000Z"
        DESCRIPTION
                "Added the complete settings subtree; reshuffled and expanded status subtree; more conforming SMIv2 mib"
        REVISION "200903130000Z"
        DESCRIPTION
                "Corrected datetimes in MIB."
        REVISION "200902240000Z"
        DESCRIPTION
                "Added info oid."
        REVISION "200902220000Z"
        DESCRIPTION
                "The intial version."

        ::= { enterprises 33120 }

-- a truth value
Boolean ::=   INTEGER { true(1), false(2) }

eZPublish       OBJECT IDENTIFIER ::= {eZSystemsMIB 1}

-- a branch where other extensions can add their oid
-- general rule: one new oid per extension below eZPublishMIB.eZPublish.extensions
extensions      OBJECT IDENTIFIER ::= {eZPublish 4}
